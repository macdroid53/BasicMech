# -*- coding: utf-8 -*-
import os 
import FreeCAD
from PySide2 import QtGui, QtCore, QtWidgets

param_grp=FreeCAD.ParamGet("User parameter:BaseApp/Preferences/General")
param_grp.SetString("AutoloadModule", "PartDesignWorkbench")
param_grp=FreeCAD.ParamGet("User parameter:Tux/PersistentToolbars/User/StartWorkbench")
param_grp.SetBool("Saved",True)
param_grp.SetString("Top", "Workbench,Macro,Break,View,Structure,Navigation")
param_grp.SetString("Left", "File")
param_grp.SetString("Right", "")
param_grp.SetString("Bottom", "")
param_grp=FreeCAD.ParamGet("User parameter:Tux/PersistentToolbars/User/PartDesignWorkbench")
param_grp.SetBool("Saved",True)
param_grp.SetString("Top", "Workbench,Macro,Break,View,Structure,Navigation")
param_grp.SetString("Left", "File")
param_grp.SetString("Right", "")
param_grp.SetString("Bottom", "")
param_grp=FreeCAD.ParamGet("User parameter:BaseApp/MainWindow/DockWindows")
param_grp.SetBool("Std_ReportView", True)
param_grp.SetBool("Std_PythonView", True)

msg="To complete the changes, restart FreeCAD!"
diag = QtWidgets.QMessageBox(QtWidgets.QMessageBox.Information, 'Restart Required', msg)
diag.setWindowModality(QtCore.Qt.ApplicationModal)
diag.exec_()
